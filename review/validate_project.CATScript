Language="VBSCRIPT"
Dim root,fso,log,errors
Sub CATMain()
 root=ResolveRoot()
 Set fso=CreateObject("Scripting.FileSystemObject")
 errors=0
 Set log=fso.CreateTextFile(root & "\review\final_validation_report.txt",True)
 log.WriteLine "CAD PROJECT FINAL VALIDATION"
 log.WriteLine "Root=" & root
 log.WriteLine "Started=" & Now

 CheckPart "Brake_Platform_2"
 CheckPart "Brake_Pedal_Shaft"
 CheckPart "Reservoir_Holder"
 CheckPart "Foot_Plate"
 CheckPart "MC_Inlet"
 CheckPart "BRK_PRS_Sensor_Connection"
 CheckPart "Pedal_Body"
 CheckAssembly root & "\Brake_Pedal_Assembly_05.CATProduct",6,False
 CheckAssembly root & "\Brake_Pedal_Assembly.CATProduct",45,True

 If errors=0 Then
  log.WriteLine "RESULT=PASS (structural/update/BOM validation)"
 Else
  log.WriteLine "RESULT=FAIL errors=" & errors
 End If
 log.WriteLine "NOTE: final visual/clash inspection in CATIA is still recommended."
 log.WriteLine "Finished=" & Now
 log.Close
 If errors>0 Then Err.Raise 514,"validate_project",CStr(errors) & " validation error(s)"
End Sub

Sub CheckPart(n)
 Dim pth,d,spa,m
 pth=root & "\final_parts\" & n & ".CATPart"
 If Not fso.FileExists(pth) Then log.WriteLine "MISSING PART: " & n:errors=errors+1:Exit Sub
 On Error Resume Next
 Set d=CATIA.Documents.Open(pth)
 If Err.Number<>0 Then log.WriteLine "OPEN FAILED: " & n & " | " & Err.Description:Err.Clear:errors=errors+1:On Error GoTo 0:Exit Sub
 On Error GoTo 0
 d.Part.Update
 Set spa=d.GetWorkbench("SPAWorkbench")
 Set m=spa.GetMeasurable(d.Part.CreateReferenceFromObject(d.Part.MainBody))
 log.WriteLine "PART " & n & " | PN=" & d.Product.PartNumber & " | UpToDate=" & d.Part.IsUpToDate(d.Part) & " | Volume_m3=" & m.Volume
 If d.Product.PartNumber<>n Then errors=errors+1:log.WriteLine "  ERROR PartNumber mismatch"
 d.Close
End Sub

Sub CheckAssembly(pth,target,isFinal)
 Dim d,p,cnt
 If Not fso.FileExists(pth) Then log.WriteLine "MISSING ASSEMBLY: " & pth:errors=errors+1:Exit Sub
 On Error Resume Next
 Set d=CATIA.Documents.Open(pth)
 If Err.Number<>0 Then log.WriteLine "ASSEMBLY OPEN FAILED: " & pth & " | " & Err.Description:Err.Clear:errors=errors+1:On Error GoTo 0:Exit Sub
 On Error GoTo 0
 Set p=d.Product:p.Update
 If isFinal Then cnt=CountBOM(p) Else cnt=p.Products.Count
 log.WriteLine "ASSEMBLY " & p.PartNumber & " | BOM=" & cnt & " | target=" & target
 If cnt<>target Then errors=errors+1:log.WriteLine "  ERROR BOM mismatch"
 d.Save:d.Close
End Sub

Function CountBOM(p)
 Dim i,ch,total,totalName
 total=0
 For i=1 To p.Products.Count
  Set ch=p.Products.Item(i):totalName=LCase(ch.Name)
  If InStr(totalName,"tilton_set")>0 Then
   total=total+1
  ElseIf ch.Products.Count=0 Then
   total=total+1
  Else
   total=total+CountBOM(ch)
  End If
 Next
 CountBOM=total
End Function

Function ResolveRoot()
 Dim sh,tmp,cfg,ts,s
 Set sh=CreateObject("WScript.Shell"):tmp=sh.ExpandEnvironmentStrings("%TEMP%"):cfg=tmp & "\CAD_Project_root.txt"
 Set fso=CreateObject("Scripting.FileSystemObject")
 If fso.FileExists(cfg) Then
  Set ts=fso.OpenTextFile(cfg,1):s=Trim(ts.ReadLine):ts.Close
  If Right(s,1)="\" Then s=Left(s,Len(s)-1)
  ResolveRoot=s
 Else
  ResolveRoot="C:\Users\Hashaam\Documents\CAD_Project"
 End If
End Function
